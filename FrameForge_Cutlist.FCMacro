# -*- coding: utf-8 -*-
import FreeCAD as App
import FreeCADGui as Gui
from PySide import QtGui, QtCore
import re
from collections import defaultdict, Counter

doc = App.ActiveDocument

# ----------------------------- ЛОГ -----------------------------
def log(msg):
    App.Console.PrintMessage(str(msg) + "\n")

# ---------------------- ОПРЕДЕЛЕНИЕ ДЛИНЫ ----------------------
def get_real_length(obj):
    """
    Реальная длина детали = максимальная длина ребра.
    Это даёт фактическую длину профиля, а не толщину.
    """
    try:
        edges = obj.Shape.Edges
        if not edges:
            return None
        return max(e.Length for e in edges)
    except:
        return None

# ---------------------- СБОР ПРОФИЛЕЙ --------------------------
def collect_profiles(name_pattern):
    regex = re.compile(name_pattern)
    profiles = defaultdict(list)

    for obj in doc.Objects:
        if not getattr(obj.ViewObject, "Visibility", False):
            continue

        if not regex.match(obj.Name):
            continue

        parts = obj.Name.split("_")
        if len(parts) < 2:
            continue

        profile_type = parts[1]
        length = get_real_length(obj)

        if length:
            profiles[profile_type].append(length)

    return profiles

# --------------------------- ДИАЛОГ ----------------------------
class ParamDialog(QtGui.QDialog):
    def __init__(self, profile_types):
        super(ParamDialog, self).__init__()
        self.setWindowTitle("Cut parameters")
        self.resize(450, 350)

        layout = QtGui.QVBoxLayout(self)

        form = QtGui.QFormLayout()

        self.kerf = QtGui.QDoubleSpinBox()
        self.kerf.setSuffix(" mm")
        self.kerf.setDecimals(2)
        self.kerf.setMaximum(50)
        self.kerf.setValue(2.0)
        form.addRow("Cut tolerance:", self.kerf)

        layout.addLayout(form)

        self.stock_boxes = {}
        self.scrap_boxes = {}

        scroll = QtGui.QScrollArea()
        scroll.setWidgetResizable(True)
        inner = QtGui.QWidget()
        inner_layout = QtGui.QFormLayout(inner)

        for p in sorted(profile_types):
            stock = QtGui.QDoubleSpinBox()
            stock.setSuffix(" mm")
            stock.setDecimals(0)
            stock.setMaximum(100000)
            stock.setSingleStep(100)
            stock.setValue(3000)

            scrap = QtGui.QLineEdit()
            scrap.setPlaceholderText("eg.: 800,1200,450")

            self.stock_boxes[p] = stock
            self.scrap_boxes[p] = scrap

            inner_layout.addRow(f"{p} — profile length:", stock)
            inner_layout.addRow(f"{p} — leftovers:", scrap)

        scroll.setWidget(inner)
        layout.addWidget(scroll)

        buttons = QtGui.QDialogButtonBox(
            QtGui.QDialogButtonBox.Ok | QtGui.QDialogButtonBox.Cancel
        )
        buttons.accepted.connect(self.accept)
        buttons.rejected.connect(self.reject)
        layout.addWidget(buttons)

    def get_values(self):
        stock = {}
        scraps = {}

        for p in self.stock_boxes:
            stock[p] = self.stock_boxes[p].value()

            txt = self.scrap_boxes[p].text().strip()
            if txt:
                scraps[p] = [float(x) for x in txt.split(",") if x.strip()]
            else:
                scraps[p] = []

        return (
            self.kerf.value(),
            stock,
            scraps
        )

# ---------------------- РАСКРОЙ -----------------------
def cut_plan(lengths, stock_len, scraps, kerf):
    lengths = sorted(lengths, reverse=True)

    bins = list(scraps)
    plans = [[] for _ in scraps]
    factory_used = 0

    def try_place(piece):
        for i in range(len(bins)):
            used_len = sum(plans[i]) + kerf * max(0, len(plans[i]))
            if bins[i] - used_len >= piece:
                plans[i].append(piece)
                return True
        return False

    for piece in lengths:
        if try_place(piece):
            continue

        bins.append(stock_len)
        plans.append([piece])
        factory_used += 1

    return plans, factory_used

# ---------------------- СТИЛИ --------------------------
HEADER_BG = (0.85, 0.85, 0.85)
ROW_BG_1 = (0.90, 0.90, 0.90)
ROW_BG_2 = (0.95, 0.95, 0.95)


def set_bg(sheet, cell, color_tuple):
    sheet.setBackground(cell, color_tuple)

# ---------------------- СПРЕДШИТЫ ------------------------------
def make_summary_sheet(summary):
    sheet = doc.addObject("Spreadsheet::Sheet", "CutList")

    headers = ["Profile type", "Length", "Amount"]
    for col, h in zip("ABC", headers):
        sheet.set(f"{col}1", h)
        set_bg(sheet, f"{col}1", HEADER_BG)

    row = 2
    stripe = False

    for p, data in summary.items():
        for length, qty in sorted(data["count"].items()):
            sheet.set(f"A{row}", p)
            sheet.set(f"B{row}", f"{length:.1f}")
            sheet.set(f"C{row}", str(qty))

            bg = ROW_BG_1 if stripe else ROW_BG_2
            for col in "ABC":
                set_bg(sheet, f"{col}{row}", bg)

            stripe = not stripe
            row += 1
            
        row += 1
        sheet.set(f"A{row}", f"Total profiles {p}")
        sheet.set(f"B{row}", str(data["stock"]))
        bg = ROW_BG_1 if stripe else ROW_BG_2
        for col in "AB":
            set_bg(sheet, f"{col}{row}", bg)
        
        stripe = not stripe
        row += 1

def make_detail_sheet(profile, stock_len, plans, kerf):
    sheet = doc.addObject("Spreadsheet::Sheet", f"CutDetails_{profile}")

    row = 1
    bar_index = 1

    for plan in plans:
        sheet.set(f"A{row}", f"Profile {bar_index} {profile}")
        sheet.set(f"B{row}", f"{stock_len:.0f}")
        set_bg(sheet, f"A{row}", HEADER_BG)
        set_bg(sheet, f"B{row}", HEADER_BG)
        row += 1

        stripe = False
        for idx, piece in enumerate(plan, 1):
            sheet.set(f"A{row}", str(idx))
            sheet.set(f"B{row}", f"{piece:.1f}")

            bg = ROW_BG_1 if stripe else ROW_BG_2
            set_bg(sheet, f"A{row}", bg)
            set_bg(sheet, f"B{row}", bg)

            stripe = not stripe
            row += 1

        total = sum(plan) + kerf * max(0, len(plan) - 1)
        leftover = stock_len - total

        sheet.set(f"A{row}", "Leftover")
        sheet.set(f"B{row}", f"{leftover:.1f}")
        set_bg(sheet, f"A{row}", HEADER_BG)
        set_bg(sheet, f"B{row}", HEADER_BG)

        row += 2
        bar_index += 1

# --------------------------- MAIN -------------------------------
profiles = collect_profiles(r"Profile_.*")

if not profiles:
    log("Profiles not found")
else:
    dlg = ParamDialog(profiles.keys())
    if dlg.exec():
        kerf, stock_len, scraps = dlg.get_values()

        summary = {}

        for p, lengths in profiles.items():
            plans, used = cut_plan(lengths, stock_len[p], scraps[p], kerf)

            summary[p] = {
                "count": Counter(round(l, 1) for l in lengths),
                "stock": used
            }

            make_detail_sheet(p, stock_len[p], plans, kerf)

        make_summary_sheet(summary)
        doc.recompute()
        log("Done.")
